#usage "update aktual libary with reference package library<p>"
       "for internal use<br>"
       "alf@cadsoft.de"

string referencepackage = "plcc-socket.lbr";
string cmd = "";

library(L) {
  if (filename(L.name) == referencepackage);
  else sprintf(cmd, "UPDATE %s;\nWRITE;\n", referencepackage);
}
exit(cmd);
