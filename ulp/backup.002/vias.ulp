// Program that counts the number of vias and its location in a board
// Generated by Cisneros Loeza Luis Enrique

int cont=0;
if (board)
  board(B) {
  output(filesetext(B.name, ".VIA")){
  printf("       V I A S\n");
  printf("Location X, Location Y\n");
  B.signals(S) { 
    S.vias(V) { 
      cont++;      
      printf("%d.-Via: (%d %d)\n",cont, V.x, V.y); 
     }    
    }  
  printf("\nNumber of vias:%d\n", cont);
  }
}
